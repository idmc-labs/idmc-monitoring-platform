FME workspace ACLED_reader.fmw

Parameters:
- year = 2019
- Reader = postgres_idmc_data_hunter   # Connection
- Writer = postgres_idmc_data_hunter   # Connection

Readers:
- POSTGRES_1: POSTGRES from $(Reader)

Writers:
- POSTGRES_2: POSTGRES to $(Writer)

Note: This is basically the ACLED downloaded modified / to download all the data for a given year - for all the countries at once
IDMC_ACLED_Downloader
    year = $(year)
    VertexCreator_Output -> DuplicateFilter
Note: some entries in acled are duplicated
DuplicateFilter
    KEYATTR = data_id
    INPUT_ORDERED_CHOICE = No
    UNIQUE -> GeometryExtractor
GeometryExtractor
    PREFER_POLYGON_OVER_SURFACE = No
    GEOHASH_PRECISION_DISPLAY = ~2.4 m (9 characters)
    KIND_LONG = Geohash
    OGCVERSION = 1.2
    OGC_WKT_PRECISION_DISPLAY = Shortened 64-bit
    ATTR = location_id
    OGEOSMS_URL_PREFIX = http://maps.google.com/?q=
    REMOVE_GEOMETRY = No
    -> UUIDGenerator
UUIDGenerator
    UUID_ATTR = uuid_acled
    -> FeatureMerger [REQUESTOR]
monitoring_platform.acled_data (reader POSTGRES_1)
    attributes: data_id int4, latitude float4, longitude varchar(255), notes text, event_date timestamp, admin1 varchar(255), gwno int4, event_id_cnty varchar(255), event_id_no_cnty varchar(255), year int4, time_precision int4, event_type varchar(255), actor1 varchar(255), ally_actor_1 varchar(255), inter1 int4, actor2 varchar(255), ally_actor_2 varchar(255), inter2 int4, interaction int4, country varchar(255), admin2 varchar(255), admin3 varchar(255), location varchar(255), geo_precision int4, source varchar(255), fatalities int4, timestamp int4
    -> FeatureMerger [SUPPLIER]
Note: according to https://knowledge.safe.com/questions/22754/filter-out-features-when-an-attribute-appears-in-a.html
FeatureMerger
    ATTR_ACCUM_MODE = Merge Supplier
    MERGE_TYPE = Attributes Only
    ATTR_CONFLICT_RES = Use Requestor
    IGNORE_NULLS = No
    SUPPLIERS_FIRST = Yes
    REJECT_NULL_MISSING_KEYS = No
    JOIN_KEYS = @Value(data_id) @Value(data_id) AUTO @Value(fatalities) @Value(fatalities) AUTO @Value(notes) @Value(notes) AUTO
    PROCESS_DUPS = No
    UNMERGED_REQUESTOR -> monitoring_platform.acled_data (writer POSTGRES_2)
monitoring_platform.acled_data (writer POSTGRES_2)
    attributes: data_id int4, latitude float4, longitude float4, notes text, event_date date, admin1 text, gwno int4, event_id_cnty text, event_id_no_cnty text, year int4, time_precision int4, event_type text, actor1 text, ally_actor_1 text, inter1 int4, actor2 text, ally_actor_2 text, inter2 int4, interaction int4, country text, admin2 text, admin3 text, location text, geo_precision int4, source text, fatalities int4, timestamp int4, location_id text, uuid_acled text

FME custom transformer IDMC_ACLED_Downloader

Parameters:
- year = 2017

Input (input)
    -> NoFeaturesTester
NoFeaturesTester
    NOINPUT -> ParameterFetcher
    -> ParameterFetcher
ParameterFetcher
    ATTR_LIST = year $(year)
    -> Tester
Tester
    TEST_MODE = Automatic
    TEST_DESCRIPTION = ""
    BOOL_OP = OR
    TEST_CLAUSE = TEST @Value(year) > 1900
    PASSED -> AttributeCreator_2
AttributeCreator_2
    ATTR_TABLE = SET_TO url = https://api.acleddata.com/acled/read?terms=accept&year=@Value(year)
    -> PythonCaller
PythonCaller
    PYTHONSYMBOL = FeatureProcessor
    PYTHONSOURCE:
      # FME PythonCaller template v1.5 - dr@inser.ch
      from fmeobjects import *
      import urllib2
      import json
      from math import *


      class FeatureProcessor(object):
          def __init__(self):
              pass

          def input(self, feature):

              i = 0
              url = feature.getAttribute('url')
              while True :
                  i+=1
                  new_url= url+'&page=%s'%i
                  response = urllib2.urlopen(feature.getAttribute('url'))
                  data = json.load(response)
                  number_of_features = len(data['data'])

                  if number_of_features == 500 :
                      feature.setAttribute('url',new_url)
                      self.pyoutput(feature)
                  else :
                      feature.setAttribute('url',new_url)
                      self.pyoutput(feature)
                      break






          def close(self):
              pass
    -> HTTPCaller
HTTPCaller
    STATUS_CODE_ATTR = _http_status_code
    SAVE_FILE = Attribute
    ERROR_ATTR = _error
    USE_COOKIES = No
    RESPONSE_HEADER_LIST_ATTR = _headers
    FOLLOW_REDIRECTS = Yes
    TARGET_ATTR_ENCODING = auto-detect
    TARGET_URL = @Value(url)
    VERIFY_SSL_CERTIFICATES = Yes
    CONNECTION_TIMEOUT_LENGTH = 60
    TARGET_ATTR = json
    HTTP_METHOD = GET
    TRANSFER_TIMEOUT_LENGTH = 90
    -> AttributeKeeper_2
AttributeKeeper_2
    KEEP_ATTRS = NAME,json
    -> JSONFlattener
JSONFlattener
    ERROR_LIST_ATTR = _json_error
    JSON_DOCUMENT = @Value(json)
    NEW_ATTRIBUTES = data
    RECURSIVE = No
    -> JSONFragmenter
JSONFragmenter
    JSON_QUERY = json[*]
    JSON_ATTR = data
    EXPLODE_FORMAT = JSON
    EXTRACT_ATTR = No
    FRAGMENTS -> JSONFlattener_2
JSONFlattener_2
    ERROR_LIST_ATTR = _json_error
    JSON_DOCUMENT = @Value(data)
    NEW_ATTRIBUTES = data_id latitude longitude notes event_date admin1 gwno event_id_cnty event_id_no_cnty event_date year time_precision event_type actor1 ally_actor_1 inter1 actor2 ally_actor_2 inter2 interaction country admin2 admin3 location geo_precision source fatalities timestamp
    RECURSIVE = No
    -> AttributeRemover
AttributeRemover
    REMOVE_ATTRS = json,data,json_type,json_index
    -> VertexCreator
VertexCreator
    YVAL = @Value(latitude)
    MODE_NAME = Replace with Point
    XVAL = @Value(longitude)
    -> DateTimeStamper
DateTimeStamper
    TIMEZONE = utc
    DATETIME_ATTR = today
    STAMP_TYPE = date
    -> DateFormatter_2
DateFormatter_2
    FMT = FME Date (%Y%m%d)
    SRCFMT = Unknown - Automatic Detection
    DATE_ATTR = today,event_date
    INVALID_DATE_VALUE = _FME_NO_OP_
    -> AttributeValidator
AttributeValidator
    TABLE = event_date;RANGE;[,@Evaluate(@Value(today))]
    PASSED -> AttributeRemover_2
AttributeRemover_2
    REMOVE_ATTRS = today
    -> DateFormatter_3
DateFormatter_3
    FMT = ISO Date (%Y-%m-%d)
    SRCFMT = Unknown - Automatic Detection
    DATE_ATTR = event_date
    INVALID_DATE_VALUE = _FME_NO_OP_
    -> VertexCreator_Output (output)
VertexCreator_Output (output)

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

INPUT (input)
    -> OUTPUT (output)
    -> Sampler
Note: Take the first input feature
Sampler
    SAMPLE_MODE = No
    RATE = 1
    SAMPLE_TYPE_LONG = First N Features
    SAMPLED -> StatisticsCalculator
OUTPUT (output)
Creator
    GEOMTYPE = Geometry Object
    NUM = 1
    CREATED -> StatisticsCalculator
Note: Count received features
StatisticsCalculator
    STATS_ATTRS = no_features
    COMPUTE_HISTOGRAM = NO
    COUNT_ATTR = NFT_count
    PREPEND_ATTR_NAME_CHOICE = For multiple results only
    SUMMARY -> Tester_2
Note: If the number of features is equal / to 1, we had no feature coming / through the Input port
Tester_2
    TEST_MODE = Automatic
    TEST_DESCRIPTION = ""
    BOOL_OP = OR
    TEST_CLAUSE = TEST @Value(NFT_count) = 1
    PASSED -> AttributeCreator
Note: Provide an attribute for filtering
AttributeCreator
    ATTR_TABLE = SET_TO no_features = true
    -> NOINPUT (output)
NOINPUT (output)
