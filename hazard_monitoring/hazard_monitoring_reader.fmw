FME workspace hazard_monitoring_reader.fmw

Parameters:
- Writer = postgres_idmc_data_hunter   # Connection
- Reader = postgres_idmc_data_hunter   # Connection
- Matemies_GitHub = https://gist.githubusercontent.com/matemies/fe0be35f4fcbd4ae2adde41241b21b2f/raw/1864d9f06f6d7a33526232533965d31ea77a3360/WD_UltraSimplified_ADM0.geojson   # Source GeoJSON File or URL

Readers:
- GEOJSON_1: GEOJSON from $(Matemies_GitHub)
- POSTGRES_1: POSTGRES from $(Reader)

Writers:
- POSTGRES_2: POSTGRES to $(Writer)

Note: This is basically the ACLED downloaded modified / to download all the data for a given year - for all the countries at once
IDMC_GDACS_Downloader
    -> AttributeExposer_2
AttributeExposer_2
    ATTR_LIST = gdacs_country,gdacs_cap,gdacs_alertlevel,gdacs_episodeid,gdacs_eventid,gdacs_eventname,gdacs_eventtype,gdacs_fromdate,gdacs_gtslink,gdacs_population,gdacs_severity,gdacs_todate,gdacs_version,gdacs_vulnerability,gdacs_year,gdacs_glide
    -> CoordinateExtractor
CoordinateExtractor
    MODE = Specify Coordinate
    Z_ATTR = _z
    Y_ATTR = _y
    IND = 0
    X_ATTR = _x
    -> DatabaseJoiner
Note: IDMC disaster type
DatabaseJoiner
    ATTR_ACCUM_MODE = Merge Joined
    CSV2_SCAN_ADDITIONAL_FIELDS = No
    CSV2_READ_SKIPPED_LINES = No
    CSV2_CASE_SENSITIVE_FIELD_NAMES = Yes
    CSV2_PRESERVE_SOURCE_ENCODING = No
    FORMAT = CSV2
    CSV2_TRIM_FIELD_VALUE_QUALIFIERS = Yes
    CSV2_FIELD_QUALIFIER_CHARACTER = "
    ATTR_CONFLICT_RES = Use Original
    ADDED_FIELDS = IDMC_id IDMC_type
    CSV2_FEATURE_TYPE_NAME = FORMAT_NAME
    CSV2_FIELD_NAMES_LINE = 1
    MATCH_MULTIPLE_DISPLAY = Create a feature for each match
    JOIN_KEYS = gdacs_eventtype GDACS_eventtype
    CSV2_TRIM_FIELD_NAME_QUALIFIERS = Yes
    CSV2_ENFORCE_STRICT_SCHEMA = No
    DATASET = https://raw.githubusercontent.com/idmc-labs/idmc-monitoring-platform/master/hazard_monitoring/IDMC_Hazard_Types_Translator.csv
    CSV2_SKIP_DUPLICATE_DELIMITERS = No
    CSV2_USE_CUSTOM_SCHEMA = NO
    CSV2_FIELD_QUALIFIER_ESCAPE_CHARACTER = "
    CSV2_DELIMITER = ,
    MATCH_RULE_DISPLAY = Match All (1:M)
    TABLE = IDMC_hazard_types
    CSV2_SCAN_MAX_ROWS = 1000
    CSV2_DATA_START_LINE = 2
    CSV2_SCAN_TYPES = No
    JOINED -> StringSearcher_Displacement
    UNJOINED -> StringSearcher_Displacement
    <REJECTED> -> StringSearcher_Displacement
Note: check if displacement is mentioned and create attribute
StringSearcher_Displacement
    STRING_TO_SEARCH = @Value(Content)
    CASE = no
    REGEXP = (displace|destro|idp)
    MATCHED_RESULT_ATTR = displacement_mentioned
    MATCHED -> AttributeCreator
    NOT_MATCHED -> AttributeCreator
AttributeCreator
    ATTR_TABLE = SET_TO displacement_mentioned = FME_CONDITIONAL:DEFAULT_VALUE'TRUE'BOOL_OP;OR;COMPOSITE_TEST;<Unused>;TEST displacement_mentioned ATTRIBUTE_IS_MISSING _FME_BLANK_STRING_'FALSE'FME_NUM_CONDITIONS2___
    -> StringSearcher_Pop
Note: pop_affected
StringSearcher_Pop
    STRING_TO_SEARCH = @Value(gdacs_population)
    CASE = no
    REGEXP = (?<=">)(.*)(?=</)
    MATCHED_RESULT_ATTR = pop_affected
    MATCHED -> StringSearcher_Severity
    NOT_MATCHED -> StringSearcher_Severity
Note: severity
StringSearcher_Severity
    STRING_TO_SEARCH = @Value(gdacs_severity)
    CASE = no
    REGEXP = (?<=">)(.*)(?=</)
    MATCHED_RESULT_ATTR = severity
    MATCHED -> StringSearcher_Vulnerability
    NOT_MATCHED -> StringSearcher_Vulnerability
Note: vulnerability
StringSearcher_Vulnerability
    STRING_TO_SEARCH = @Value(gdacs_vulnerability)
    CASE = no
    REGEXP = (?<=">)(.*)(?=</)
    MATCHED_RESULT_ATTR = vulnerability
    MATCHED -> StringSearcher
    NOT_MATCHED -> StringSearcher
Note: Hazard_Type
StringSearcher
    STRING_TO_SEARCH = @Value(severity)
    CASE = no
    REGEXP = ^[^\(]+
    MATCHED_RESULT_ATTR = Hazard_Type
    MATCHED -> DateFormatter
    NOT_MATCHED -> DateFormatter
Note: From time zone format to iso date
DateFormatter
    INVALID_DATE_VALUE = _FME_NO_OP_
    DATE_ATTR = gdacs_fromdate,PublishedDate,gdacs_todate
    SRCFMT = Unknown - Automatic Detection
    FMT = ISO Date (%Y-%m-%d)
    -> NeighborFinder_2 [BASE]
WD (reader GEOJSON_1)
    attributes: OBJECTID int, ISO3 string, Short_Name string, Latitude int, Longitude int, Name string, Region string, ISO2 string
    -> NeighborFinder_2 [CANDIDATE]
Note: ISO3 / Short_Name
NeighborFinder_2
    ATTR_ACCUM_MODE = Merge Candidate
    INSERT_VERTEX = No
    CANDIDATES_FIRST = No
    MEASURE_TYPE = Continuous
    MAX = 60
    K = 1
    TREAT_POLYGON_AS = Areas
    MODE = Bases and Candidates
    ATTR_CONFLICT_RES = Use Base
    MATCHED -> AttributeTrimmer_2
    UNMATCHED_BASE -> AttributeTrimmer_2
AttributeTrimmer_2
    TRIM_CHARS = [^0-9A-Z];
    TRIM_TO_NONE = Yes
    TRIM_TYPE = Both
    SRC_ATTRS = Hazard_Type
    -> StringReplacer
Note: To delete tabs that where not deleted with the trimmer "sgt;"
StringReplacer
    CASE = NO
    REGEXP = NO
    SRC_ATTRS = Hazard_Type
    NO_MATCH = _FME_NO_OP_
    FIND_TEXT = "&gt; "
    -> UUIDGenerator
UUIDGenerator
    UUID_ATTR = uuid
    -> GeometryExtractor
GeometryExtractor
    GEOHASH_PRECISION_DISPLAY = ~2.4 m (9 characters)
    REMOVE_GEOMETRY = No
    OGC_WKT_PRECISION_DISPLAY = Shortened 64-bit
    ATTR = location_id
    PREFER_POLYGON_OVER_SURFACE = No
    OGEOSMS_URL_PREFIX = http://maps.google.com/?q=
    OGCVERSION = 1.2
    KIND_LONG = Geohash
    -> GDACS_Output
Note: Edition of output table
GDACS_Output: AttributeManager
    ATTR_TABLE:
      RENAME_SET_VALUE uuid > uuid_hazard
      RENAME_SET_VALUE gdacs_eventid > event_id
      RENAME_SET_VALUE Title > event_name
      SET_TO idmc_event_name = @Value(gdacs_country): @Value(IDMC_type) - @Value(gdacs_fromdate)
      SET_TO displacement_type = Disaster
      RENAME_SET_VALUE IDMC_id > hazard_type_id
      RENAME_SET_VALUE IDMC_type > hazard_type
      RENAME_SET_VALUE gdacs_glide > glide_number
      RENAME_SET_VALUE Content > comment
      RENAME_SET_VALUE gdacs_fromdate > start_date
      RENAME_SET_VALUE gdacs_todate > end_date
      RENAME_SET_VALUE ISO3 > iso3
      RENAME_SET_VALUE Short_Name > country
      RENAME_SET_VALUE gdacs_country > countries_affected
      SET_TO iso3_affected
      SET_TO source_name = GDACS
      RENAME_SET_VALUE LinkURI > source_url
      RENAME_SET_VALUE PublishedDate > pub_date
      RENAME_SET_VALUE gdacs_eventtype > hazard_code_source
      SET_TO hazard_type_source
      RENAME_SET_VALUE gdacs_alertlevel > alert_score
      RENAME_SET_VALUE _y > latitude
      RENAME_SET_VALUE _x > longitude
      SET_TO exposed_50
      SET_TO exposed_20
      SET_TO exposed_5
      RENAME_SET_VALUE pop_affected > affected
      SET_TO evacuations
      SET_TO homeless
      SET_TO injured
      SET_TO fatalities
      REMOVE Id
      REMOVE gdacs_cap
      REMOVE gdacs_episodeid
      REMOVE gdacs_gtslink
      REMOVE gdacs_population
      REMOVE gdacs_severity
      REMOVE gdacs_version
      REMOVE gdacs_vulnerability
      REMOVE gdacs_year
      REMOVE _z
      REMOVE severity
      REMOVE vulnerability
      REMOVE OBJECTID
      REMOVE Latitude
      REMOVE Longitude
      REMOVE Name
      REMOVE Region
      REMOVE ISO2
      REMOVE _distance
      REMOVE _angle
      REMOVE _candidate_angle
      REMOVE _candidate_label_angle
      REMOVE _closest_candidate_x
      REMOVE _closest_candidate_y
      REMOVE _closest_base_x
      REMOVE _closest_base_y
      REMOVE Hazard_Type
      REMOVE Summary
      REMOVE Copyright
      REMOVE LastUpdate
      REMOVE Category
      REMOVE Author
      REMOVE _georss_feature_number
      REMOVE _matched_records
      REMOVE fme_rejection_code
      REMOVE gdacs_eventname
    -> DuplicateFilter
DuplicateFilter
    KEYATTR = pub_date event_id
    INPUT_ORDERED_CHOICE = No
    UNIQUE -> FeatureMerger [REQUESTOR]
monitoring_platform.hazard_data (reader POSTGRES_1)
    attributes: uuid varchar(255), event_id varchar(255), event_name varchar(255), idmc_event_name varchar(255), displacement_type varchar(255), hazard_type_id varchar(255), glide_number varchar(255), comment varchar(255), start_date date, end_date date, iso3 varchar(255), countries_affected varchar(255), iso3_affected varchar(255), source_name varchar(255), source_url varchar(255), pub_date date, hazard_code_source varchar(255), hazard_type_source varchar(255), alert_score varchar(255), latitude float4, longitude float4, displacement_mentioned varchar(255), exposed_50 varchar(255), exposed_20 varchar(255), exposed_5 varchar(255), affected varchar(255), evacuations varchar(255), homeless varchar(255), injured varchar(255), fatalities varchar(255)
    -> DateFormatter_2
DateFormatter_2
    INVALID_DATE_VALUE = _FME_NO_OP_
    DATE_ATTR = pub_date
    SRCFMT = Unknown - Automatic Detection
    FMT = ISO Date (%Y-%m-%d)
    -> DuplicateFilter_2
DuplicateFilter_2
    KEYATTR = event_id
    INPUT_ORDERED_CHOICE = No
    UNIQUE -> FeatureMerger [SUPPLIER]
FeatureMerger
    ATTR_ACCUM_MODE = Merge Supplier
    PROCESS_DUPS = No
    MERGE_TYPE = Attributes Only
    JOIN_KEYS = @Value(event_id) @Value(event_id) AUTO
    REJECT_NULL_MISSING_KEYS = No
    SUPPLIERS_FIRST = No
    IGNORE_NULLS = No
    ATTR_CONFLICT_RES = Use Requestor
    MERGED -> AttributeCreator_2
    UNMERGED_REQUESTOR -> AttributeCreator_3
AttributeCreator_2
    ATTR_TABLE = SET_TO fme_db_operation = UPDATE
    -> AttributeRemover
AttributeRemover
    REMOVE_ATTRS = uuid,uuid_hazard
    -> monitoring_platform.hazard_data (writer POSTGRES_2)
AttributeCreator_3
    ATTR_TABLE = SET_TO fme_db_operation = INSERT
    -> monitoring_platform.hazard_data (writer POSTGRES_2)
monitoring_platform.hazard_data (writer POSTGRES_2)
    attributes: location_id text, uuid_hazard text, event_id text, event_name text, idmc_event_name text, displacement_type text, hazard_type_id int4, hazard_type text, glide_number text, comment text, start_date date, end_date date, iso3 text, country text, countries_affected text, iso3_affected text, source_name text, source_url text, pub_date date, hazard_code_source text, hazard_type_source text, alert_score text, latitude float4, longitude float4, displacement_mentioned bool, exposed_50 int4, exposed_20 int4, exposed_5 int4, affected text, evacuations int4,
      homeless int4, injured int4, fatalities int4

FME custom transformer IDMC_GDACS_Downloader

Input (input)
    -> NoFeaturesTester
NoFeaturesTester
    NOINPUT -> AttributeCreator
    -> AttributeCreator
AttributeCreator
    ATTR_TABLE = SET_TO url = http://www.gdacs.org/xml/rss_7d.xml
    -> GeoRSSFeatureReader
GeoRSSFeatureReader
    GEORSS_ATTR = url
    MERGE_CHOICES = No
    GEORSS_MODE = NORMAL
    INVALID_GEORSS_CHOICES = No
    FEAT_NUM = _georss_feature_number
    ENTRY -> Output (output)
Output (output)
PythonCaller_Archive [off]
    PYTHONSOURCE:
      # GDACS PythonCaller template leonardo.milano@idmc.ch - python 3
      from fmeobjects import *
      #import pandas as pd
      from datetime import timedelta, date

      class FeatureProcessor(object):
          def __init__(self):
              pass

          def input(self, feature):
              year=feature.getAttribute('year')
              url = "http://www.gdacs.org/rss.aspx?profile=ARCHIVE&fromarchive=true&from={}&to={}"

              def daterange(start_date, end_date):
                  for n in range(int ((end_date - start_date).days)):
                      yield start_date + timedelta(n)

              start_date = date(int(year), 1, 1)
              end_date   = date(int(year)+1, 1, 1)
              end_date   = date(int(year), 1, 10)

              for single_date in daterange(start_date, end_date):
                  new_url = url.format(single_date,single_date)
                  feature.setAttribute('url',new_url)
                  self.pyoutput(feature)
              #url='http://www.gdacs.org/xml/rss_7d.xml'
              #feature.setAttribute('url',new_url)
              #self.pyoutput(feature)

          def close(self):
              pass
    PYTHONSYMBOL = FeatureProcessor

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

INPUT (input)
    -> OUTPUT (output)
    -> Sampler
Note: Take the first input feature
Sampler
    SAMPLE_TYPE_LONG = First N Features
    RATE = 1
    SAMPLE_MODE = No
    SAMPLED -> StatisticsCalculator
OUTPUT (output)
Creator
    GEOMTYPE = Geometry Object
    NUM = 1
    CREATED -> StatisticsCalculator
Note: Count received features
StatisticsCalculator
    PREPEND_ATTR_NAME_CHOICE = For multiple results only
    STATS_ATTRS = no_features
    COMPUTE_HISTOGRAM = NO
    COUNT_ATTR = NFT_count
    SUMMARY -> Tester_2
Note: If the number of features is equal / to 1, we had no feature coming / through the Input port
Tester_2
    TEST_CLAUSE = TEST @Value(NFT_count) = 1
    TEST_MODE = Automatic
    TEST_DESCRIPTION = ""
    BOOL_OP = OR
    PASSED -> AttributeCreator
Note: Provide an attribute for filtering
AttributeCreator
    ATTR_TABLE = SET_TO no_features = true
    -> NOINPUT (output)
NOINPUT (output)
