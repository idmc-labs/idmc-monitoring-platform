FME workspace cat_nat_component.fmw

Parameters:
- SourceDataset_XML = https://www.catnat.net/index.php?option=com_obrss&task=feed&id=52   # Source XML File(s)
- FEATURE_TYPES =
- DestDataset_CSV2 = /Users/milano/IDMC/MonitoringPlatform/idmc-monitoring-platform/hazard_monitoring   # Destination CSV (Comma Separated Value) Folder
- SourceDataset_GEOJSON_3 = https://gist.githubusercontent.com/matemies/fe0be35f4fcbd4ae2adde41241b21b2f/raw/1864d9f06f6d7a33526232533965d31ea77a3360/WD_UltraSimplified_ADM0.geojson   # Source GeoJSON File or URL
- DestDataset_XLSXW = $(FME_MF_DIR)idmc_hazard_monitoring_reader.xlsx   # Destination Microsoft Excel File
- DestDataset_POSTGRES = postgres_idmc_data_hunter   # Connection
- SourceDataset_POSTGRES = postgres_idmc_data_hunter   # Connection

Readers:
- XML_1: XML from $(SourceDataset_XML)
- GEOJSON_1: GEOJSON from $(SourceDataset_GEOJSON_3)
- POSTGRES_1: POSTGRES from $(SourceDataset_POSTGRES)

Writers:
- CSV2_1: CSV2 to $(DestDataset_CSV2)
- XLSXW_1: XLSXW to $(DestDataset_XLSXW)
- POSTGRES_2: POSTGRES to $(DestDataset_POSTGRES)

Note: This is basically the ACLED downloaded modified / to download all the data for a given year - for all the countries at once
IDMC_GDACS_Downloader
    year = 2017
    -> AttributeExposer_2
AttributeExposer_2
    ATTR_LIST = gdacs_country,gdacs_cap,gdacs_alertlevel,gdacs_episodeid,gdacs_eventid,gdacs_eventname,gdacs_eventtype,gdacs_fromdate,gdacs_gtslink,gdacs_population,gdacs_severity,gdacs_todate,gdacs_version,gdacs_vulnerability,gdacs_year,gdacs_glide
    -> DatabaseJoiner
Note: IDMC disaster type
DatabaseJoiner
    CSV2_SCAN_ADDITIONAL_FIELDS = No
    CSV2_SCAN_TYPES = No
    CSV2_DELIMITER = ,
    CSV2_DATA_START_LINE = 2
    CSV2_PRESERVE_SOURCE_ENCODING = No
    TABLE = IDMC_hazard_types
    CSV2_FIELD_QUALIFIER_CHARACTER = "
    DATASET = https://raw.githubusercontent.com/idmc-labs/idmc-monitoring-platform/master/hazard_monitoring/IDMC_Hazard_Types_Translator.csv
    CSV2_ENFORCE_STRICT_SCHEMA = No
    CSV2_TRIM_FIELD_NAME_QUALIFIERS = Yes
    CSV2_CASE_SENSITIVE_FIELD_NAMES = Yes
    FORMAT = CSV2
    CSV2_SKIP_DUPLICATE_DELIMITERS = No
    CSV2_TRIM_FIELD_VALUE_QUALIFIERS = Yes
    CSV2_FEATURE_TYPE_NAME = FORMAT_NAME
    MATCH_MULTIPLE_DISPLAY = Create a feature for each match
    CSV2_FIELD_QUALIFIER_ESCAPE_CHARACTER = "
    ATTR_ACCUM_MODE = Merge Joined
    CSV2_USE_CUSTOM_SCHEMA = NO
    JOIN_KEYS = gdacs_eventtype GDACS_eventtype
    MATCH_RULE_DISPLAY = Match All (1:M)
    ATTR_CONFLICT_RES = Use Original
    CSV2_FIELD_NAMES_LINE = 1
    CSV2_READ_SKIPPED_LINES = No
    CSV2_SCAN_MAX_ROWS = 1000
    ADDED_FIELDS = IDMC_id IDMC_type
    JOINED -> CoordinateExtractor
    UNJOINED -> CoordinateExtractor
    <REJECTED> -> CoordinateExtractor
CoordinateExtractor
    Z_ATTR = _z
    Y_ATTR = _y
    MODE = Specify Coordinate
    IND = 0
    X_ATTR = _x
    -> StringSearcher_Displacement
Note: check if displacement is mentioned and create attribute
StringSearcher_Displacement
    CASE = no
    REGEXP = (?:displace|evacu|destro|idp)
    STRING_TO_SEARCH = @Value(Content)
    MATCHED_RESULT_ATTR = displacement_mentioned
    MATCHED -> AttributeCreator
    NOT_MATCHED -> AttributeCreator
AttributeCreator
    ATTR_TABLE = SET_TO displacement_mentioned = FME_CONDITIONAL:DEFAULT_VALUE'FALSE'BOOL_OP;OR;COMPOSITE_TEST;<Unused>;TEST @Value(displacement_mentioned) CONTAINS TRUE'TRUE'FME_NUM_CONDITIONS2___
    -> StringSearcher_Pop
Note: pop_affected
StringSearcher_Pop
    CASE = no
    REGEXP = (?<=">)(.*)(?=</)
    STRING_TO_SEARCH = @Value(gdacs_population)
    MATCHED_RESULT_ATTR = pop_affected
    MATCHED -> StringSearcher_Severity
    NOT_MATCHED -> StringSearcher_Severity
Note: severity
StringSearcher_Severity
    CASE = no
    REGEXP = (?<=">)(.*)(?=</)
    STRING_TO_SEARCH = @Value(gdacs_severity)
    MATCHED_RESULT_ATTR = severity
    MATCHED -> StringSearcher_Vulnerability
    NOT_MATCHED -> StringSearcher_Vulnerability
Note: vulnerability
StringSearcher_Vulnerability
    CASE = no
    REGEXP = (?<=">)(.*)(?=</)
    STRING_TO_SEARCH = @Value(gdacs_vulnerability)
    MATCHED_RESULT_ATTR = vulnerability
    MATCHED -> StringSearcher
    NOT_MATCHED -> StringSearcher
Note: Hazard_Type
StringSearcher
    CASE = no
    REGEXP = ^[^\(]+
    STRING_TO_SEARCH = @Value(severity)
    MATCHED_RESULT_ATTR = Hazard_Type
    MATCHED -> DateFormatter
    NOT_MATCHED -> DateFormatter
Note: From time zone format to iso date
DateFormatter
    SRCFMT = Unknown - Automatic Detection
    DATE_ATTR = gdacs_fromdate,PublishedDate,gdacs_todate
    FMT = ISO Date (%Y-%m-%d)
    INVALID_DATE_VALUE = _FME_NO_OP_
    -> NeighborFinder_2 [BASE]
Note: CatNat
element (reader XML_1) [off]
    attributes: ID xml_decimal(6,0), affected xml_decimal(7,0), article{} xml_char(10264), article{}.link xml_decimal(6,0), article{}.title xml_char(99), continent xml_char(8), cost xml_decimal(2,0), country xml_char(15), enddate xml_char(11), evacuees xml_decimal(6,0), fips xml_char(3), hazard xml_char(25), hazardcode xml_decimal(3,0), homeless xml_decimal(4,0), id_article xml_decimal(6,0), indexes.event_gravity_indice xml_decimal(2,0), indexes.human_csq_indice xml_decimal(2,0), indexes.material_csq_indice xml_decimal(2,0), injured xml_decimal(4,0), killed xml_decimal(4,0), latitude xml_decimal(8,4), localisation xml_char(17), longitude xml_decimal(9,4), month xml_char(5), origincode xml_char(6), originhazard xml_char(13), others_countries xml_char(9), others_countries.fips xml_char(3), others_countries.fips{} xml_char(3), peril xml_char(30),
      perilcode xml_char(4), startdate xml_char(11), sub_continent xml_char(24), subperil xml_char(17), subperilcode xml_char(5), titlearticle xml_char(99), xml_fragment xml_xml, xml_id xml_char(16), xml_matched_element xml_char(8), xml_parent_child_pos xml_char(1), xml_parent_id xml_char(1), year xml_decimal(5,0)
    -> AttributeExposer
AttributeExposer [off]
    ATTR_LIST = article{},others_countries.fips{}
    -> SubstringExtractor
Note: Extract contect from article list
SubstringExtractor [off]
    SRC_STRING = @Value(article{1})
    RESULT_ATTR = article
    END = -1
    START = 0
    -> AttributeTrimmer
Note: Delete tabs
AttributeTrimmer [off]
    TRIM_TYPE = Both
    SRC_ATTRS = article
    TRIM_TO_NONE = Yes
    -> TimeStamper
TimeStamper [off]
    TIME_ATTR = _timestamp
    FMT = ^d/^m/^Y
    -> VertexCreator
Note: Generate clean geometry
VertexCreator [off]
    YVAL = @Value(latitude)
    XVAL = @Value(longitude)
    MODE_NAME = Add Point
    -> DatabaseJoiner_2
DatabaseJoiner_2 [off]
    CSV2_SCAN_ADDITIONAL_FIELDS = No
    CSV2_SCAN_TYPES = No
    CSV2_DATA_START_LINE = 2
    CSV2_DELIMITER = ,
    CSV2_PRESERVE_SOURCE_ENCODING = No
    TABLE = IDMC_hazard_types
    CSV2_FIELD_QUALIFIER_CHARACTER = "
    DATASET = $(FME_MF_DIR_ENCODED)IDMC_Hazard_Types3.csv
    CSV2_ENFORCE_STRICT_SCHEMA = No
    CSV2_TRIM_FIELD_NAME_QUALIFIERS = Yes
    CSV2_CASE_SENSITIVE_FIELD_NAMES = Yes
    FORMAT = CSV2
    CSV2_SKIP_DUPLICATE_DELIMITERS = No
    CSV2_TRIM_FIELD_VALUE_QUALIFIERS = Yes
    CSV2_FEATURE_TYPE_NAME = FORMAT_NAME
    MATCH_MULTIPLE_DISPLAY = Create a feature for each match
    CSV2_FIELD_QUALIFIER_ESCAPE_CHARACTER = "
    ATTR_ACCUM_MODE = Merge Joined
    CSV2_USE_CUSTOM_SCHEMA = NO
    JOIN_KEYS = hazardcode CATNAT_HazardCode
    MATCH_RULE_DISPLAY = Match All (1:M)
    ATTR_CONFLICT_RES = Use Original
    CSV2_FIELD_NAMES_LINE = 1
    CSV2_SCAN_MAX_ROWS = 1000
    CSV2_READ_SKIPPED_LINES = No
    ADDED_FIELDS = IDMC_id
    JOINED -> NeighborFinder [BASE]
    UNJOINED -> NeighborFinder [BASE]
Note: ISO3 calculation based on / IDMC simplified referential
NeighborFinder [off]
    MAX = 30
    CANDIDATES_FIRST = No
    INSERT_VERTEX = No
    ATTR_CONFLICT_RES = Use Base
    K = 1
    TREAT_POLYGON_AS = Areas
    MODE = Bases and Candidates
    ATTR_ACCUM_MODE = Merge Candidate
    MEASURE_TYPE = Continuous
    MATCHED -> CATNAT_Output
Note: Edition of output table
CATNAT_Output: AttributeManager [off]
    ATTR_TABLE:
      SET_TO affected > population_afected
      SET_TO affected = @Value(affected)
      RENAME_SET_VALUE country
      SET_TO hazardcode > hazard_code_source = @Value(hazardcode)
      RENAME_SET_VALUE indexes.event_gravity_indice > indexes_event_gravity_indice
      RENAME_SET_VALUE indexes.human_csq_indice > indexes_human_csq_indice
      RENAME_SET_VALUE indexes.material_csq_indice > indexes_material_csq_indice
      RENAME_SET_VALUE titlearticle > original_title
      REMOVE xml_fragment
      REMOVE xml_id
      REMOVE xml_matched_element
      REMOVE xml_parent_child_pos
      REMOVE xml_parent_id
      REMOVE fme_feature_type
      REMOVE article{}
      RENAME_SET_VALUE article > content
      SET_TO displacement_mentioned = FME_CONDITIONAL:DEFAULT_VALUE'FALSE'BOOL_OP;OR;COMPOSITE_TEST;<Unused>;TEST @Value(evacuees) > 0'TRUE'BOOL_OP;OR;COMPOSITE_TEST;<Unused>;TEST @Value(homeless) > 0'TRUE'FME_NUM_CONDITIONS3___
      SET_TO = alert_level
      SET_TO = cap
      SET_TO = countries_afected
      SET_TO = linkuri
      SET_TO db_source = CatNat
      REMOVE OBJECTID
      RENAME_SET_VALUE Short_Name > short_name
      REMOVE Latitude
      REMOVE Longitude
      REMOVE Name
      REMOVE Region
      REMOVE ISO2
      REMOVE _distance
      REMOVE _angle
      REMOVE _candidate_angle
      REMOVE _candidate_label_angle
      REMOVE _closest_candidate_x
      REMOVE _closest_candidate_y
      REMOVE _closest_base_x
      REMOVE _closest_base_y
      SET_TO idmc_name = @Value(country): @Value(hazard) - @Value(startdate)
WD (reader GEOJSON_1)
    attributes: OBJECTID int, ISO3 string, Short_Name string, Latitude int, Longitude int, Name string, Region string, ISO2 string
    -> NeighborFinder_2 [CANDIDATE]
Note: ISO3 / Short_Name
NeighborFinder_2
    MAX = 60
    CANDIDATES_FIRST = No
    INSERT_VERTEX = No
    ATTR_CONFLICT_RES = Use Base
    K = 1
    TREAT_POLYGON_AS = Areas
    MODE = Bases and Candidates
    ATTR_ACCUM_MODE = Merge Candidate
    MEASURE_TYPE = Continuous
    MATCHED -> AttributeTrimmer_2
    UNMATCHED_BASE -> AttributeTrimmer_2
AttributeTrimmer_2
    TRIM_TYPE = Both
    SRC_ATTRS = Hazard_Type
    TRIM_CHARS = [^0-9A-Z];
    TRIM_TO_NONE = Yes
    -> StringReplacer
Note: To delete tabs that where not deleted with the trimmer "sgt;"
StringReplacer
    REGEXP = NO
    CASE = NO
    SRC_ATTRS = Hazard_Type
    FIND_TEXT = "&gt; "
    NO_MATCH = _FME_NO_OP_
    -> UUIDGenerator
UUIDGenerator
    UUID_ATTR = uuid
    -> GDACS_Output
Note: Edition of output table
Note: CHECK what's already in the database
GDACS_Output: AttributeManager
    ATTR_TABLE:
      RENAME_SET_VALUE gdacs_eventid > event_id
      RENAME_SET_VALUE Title > event_name
      SET_TO idmc_event_name = @Value(gdacs_country): @Value(IDMC_type) - @Value(gdacs_fromdate)
      SET_TO displacement_type = Disaster
      RENAME_SET_VALUE IDMC_id > hazard_type_id
      RENAME_SET_VALUE gdacs_glide > glide_number
      RENAME_SET_VALUE Content > comment
      RENAME_SET_VALUE gdacs_fromdate > start_date
      RENAME_SET_VALUE gdacs_todate > end_date
      RENAME_SET_VALUE ISO3 > iso3
      RENAME_SET_VALUE gdacs_country > countries_affected
      SET_TO iso3_affected
      SET_TO source_name = GDACS
      RENAME_SET_VALUE LinkURI > source_url
      RENAME_SET_VALUE PublishedDate > pub_date
      RENAME_SET_VALUE gdacs_eventtype > hazard_code_source
      SET_TO hazard_type_source
      RENAME_SET_VALUE gdacs_alertlevel > alert_score
      RENAME_SET_VALUE _y > latitude
      RENAME_SET_VALUE _x > longitude
      SET_TO exposed_50
      SET_TO exposed_20
      SET_TO exposed_5
      RENAME_SET_VALUE pop_affected > affected
      SET_TO evacuations
      SET_TO homeless
      SET_TO injured
      SET_TO fatalities
      REMOVE Id
      REMOVE gdacs_cap
      REMOVE gdacs_episodeid
      REMOVE gdacs_gtslink
      REMOVE gdacs_population
      REMOVE gdacs_severity
      REMOVE gdacs_version
      REMOVE gdacs_vulnerability
      REMOVE gdacs_year
      REMOVE _z
      REMOVE severity
      REMOVE vulnerability
      REMOVE OBJECTID
      REMOVE Short_Name
      REMOVE Latitude
      REMOVE Longitude
      REMOVE Name
      REMOVE Region
      REMOVE ISO2
      REMOVE _distance
      REMOVE _angle
      REMOVE _candidate_angle
      REMOVE _candidate_label_angle
      REMOVE _closest_candidate_x
      REMOVE _closest_candidate_y
      REMOVE _closest_base_x
      REMOVE _closest_base_y
      REMOVE Hazard_Type
      REMOVE Summary
      REMOVE Copyright
      REMOVE LastUpdate
      REMOVE Category
      REMOVE Author
      REMOVE _georss_feature_number
      REMOVE _matched_records
      REMOVE fme_rejection_code
      REMOVE gdacs_eventname
      REMOVE IDMC_type
    -> DuplicateFilter
DuplicateFilter
    INPUT_ORDERED_CHOICE = No
    KEYATTR = pub_date event_id
    UNIQUE -> FeatureMerger [REQUESTOR]
monitoring_platform.hazard_data (reader POSTGRES_1)
    attributes: uuid varchar(255), event_id varchar(255), event_name varchar(255), idmc_event_name varchar(255), displacement_type varchar(255), hazard_type_id varchar(255), glide_number varchar(255), comment varchar(255), start_date date, end_date date, iso3 varchar(255), countries_affected varchar(255), iso3_affected varchar(255), source_name varchar(255), source_url varchar(255), pub_date date, hazard_code_source varchar(255), hazard_type_source varchar(255), alert_score varchar(255), latitude float4, longitude float4, displacement_mentioned varchar(255), exposed_50 varchar(255), exposed_20 varchar(255), exposed_5 varchar(255), affected varchar(255), evacuations varchar(255), homeless varchar(255), injured varchar(255), fatalities varchar(255)
    -> DateFormatter_2
DateFormatter_2
    SRCFMT = Unknown - Automatic Detection
    DATE_ATTR = pub_date
    FMT = ISO Date (%Y-%m-%d)
    INVALID_DATE_VALUE = _FME_NO_OP_
    -> DuplicateFilter_2
DuplicateFilter_2
    INPUT_ORDERED_CHOICE = No
    KEYATTR = pub_date event_id
    UNIQUE -> FeatureMerger [SUPPLIER]
FeatureMerger
    REJECT_NULL_MISSING_KEYS = No
    JOIN_KEYS = @Value(event_id) @Value(event_id) AUTO @Value(pub_date) @Value(pub_date) AUTO
    IGNORE_NULLS = No
    ATTR_CONFLICT_RES = Use Requestor
    SUPPLIERS_FIRST = No
    ATTR_ACCUM_MODE = Merge Supplier
    MERGE_TYPE = Attributes Only
    PROCESS_DUPS = No
    UNMERGED_REQUESTOR -> monitoring_platform.hazard_data (writer POSTGRES_2)
monitoring_platform.hazard_data (writer POSTGRES_2)
    attributes: id int4, affected int4, continent varchar(8), cost int2, country varchar(15), enddate varchar(11), evacuees int4, fips varchar(3), hazard varchar(25), hazardcode int2, homeless int2, id_article int4, indexes_event_gravity_indice int2, indexes_human_csq_indice int2, indexes_material_csq_indice int2, injured int2, killed int2, latitude numeric(8,4), localisation varchar(17), longitude numeric(9,4), month varchar(5), origincode varchar(6), originhazard varchar(13), others_countries varchar(9), others_countries_fips varchar(3), others_countries_fips{} varchar(3), peril varchar(30), perilcode varchar(4), startdate varchar(11), sub_continent varchar(24),
      subperil varchar(17), subperilcode varchar(5), titlearticle varchar(99), xml_fragment xml, xml_id varchar(16), xml_matched_element varchar(8), xml_parent_child_pos varchar(1), xml_parent_id varchar(1), year int4

FME custom transformer IDMC_GDACS_Downloader

Parameters:
- year = 2017

Input (input)
    -> NoFeaturesTester
NoFeaturesTester
    NOINPUT -> ParameterFetcher
    -> ParameterFetcher
ParameterFetcher
    ATTR_LIST = year $(year)
    -> Tester
Tester
    TEST_CLAUSE = TEST @Value(year) > 1900
    BOOL_OP = OR
    TEST_MODE = Automatic
    TEST_DESCRIPTION = ""
    PASSED -> AttributeCreator
AttributeCreator
    ATTR_TABLE = SET_TO url
    -> PythonCaller
PythonCaller
    PYTHONSYMBOL = FeatureProcessor
    PYTHONSOURCE:
      # GDACS PythonCaller template leonardo.milano@idmc.ch - python 3
      from fmeobjects import *
      #import pandas as pd
      from datetime import timedelta, date

      class FeatureProcessor(object):
          def __init__(self):
              pass

          def input(self, feature):
              year=feature.getAttribute('year')
              url = "http://www.gdacs.org/rss.aspx?profile=ARCHIVE&fromarchive=true&from={}&to={}"

              def daterange(start_date, end_date):
                  for n in range(int ((end_date - start_date).days)):
                      yield start_date + timedelta(n)

              start_date = date(int(year), 1, 1)
              end_date   = date(int(year)+1, 1, 1)
              #end_date   = date(int(year), 1, 3)

              for single_date in daterange(start_date, end_date):
                  new_url = url.format(single_date,single_date)
                  feature.setAttribute('url',new_url)
                  self.pyoutput(feature)
          #print single_date.strftime("%Y-%m-%d")
              #daterange = pd.date_range("{}-01-01".format(year),"{}-01-01".format(year))
              #for date in daterange:
                  #day=date.strftime("%Y-%m-%d")
                  #new_url = url.format(day,day)
                  #feature.setAttribute('url',new_url)
                  #self.pyoutput(feature)

          def close(self):
              pass
    -> GeoRSSFeatureReader
GeoRSSFeatureReader
    GEORSS_MODE = NORMAL
    GEORSS_ATTR = url
    MERGE_CHOICES = No
    INVALID_GEORSS_CHOICES = Yes
    FEAT_NUM = _georss_feature_number
    ENTRY -> Output (output)
Output (output)

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

INPUT (input)
    -> OUTPUT (output)
    -> Sampler
Note: Take the first input feature
Sampler
    SAMPLE_MODE = No
    RATE = 1
    SAMPLE_TYPE_LONG = First N Features
    SAMPLED -> StatisticsCalculator
OUTPUT (output)
Creator
    GEOMTYPE = Geometry Object
    NUM = 1
    CREATED -> StatisticsCalculator
Note: Count received features
StatisticsCalculator
    COMPUTE_HISTOGRAM = NO
    STATS_ATTRS = no_features
    COUNT_ATTR = NFT_count
    PREPEND_ATTR_NAME_CHOICE = For multiple results only
    SUMMARY -> Tester_2
Note: If the number of features is equal / to 1, we had no feature coming / through the Input port
Tester_2
    TEST_CLAUSE = TEST @Value(NFT_count) = 1
    BOOL_OP = OR
    TEST_MODE = Automatic
    TEST_DESCRIPTION = ""
    PASSED -> AttributeCreator
Note: Provide an attribute for filtering
AttributeCreator
    ATTR_TABLE = SET_TO no_features = true
    -> NOINPUT (output)
NOINPUT (output)
