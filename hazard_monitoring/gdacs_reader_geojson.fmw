FME workspace gdacs_reader_geojson.fmw

Parameters:
- SourceDataset_POSTGRES_6 = postgres_idmc_data_hunter   # Connection
- Writer = postgres_idmc_data_hunter   # Connection

Readers:
- POSTGRES_1: POSTGRES from $(SourceDataset_POSTGRES_6)

Writers:
- POSTGRES_2: POSTGRES to $(Writer)

Note: This is basically the ACLED downloaded modified / to download all the data for a given year - for all the countries at once
IDMC_GDACS_Downloader
    -> AttributeExposer_2
AttributeExposer_2
    ATTR_LIST = gdacs_country,gdacs_cap,gdacs_alertlevel,gdacs_episodeid,gdacs_eventid,gdacs_eventname,gdacs_eventtype,gdacs_fromdate,gdacs_gtslink,gdacs_todate,gdacs_version,gdacs_year,gdacs_glide,gdacs_vulnerability,gdacs_population,gdacs_severity,gdacs_resources
    -> StringSearcher
StringSearcher
    CASE = no
    REGEXP = http.{0,100}\.geojson
    MATCHED_RESULT_ATTR = gdacs_geojson_link
    STRING_TO_SEARCH = @Value(gdacs_resources)
    MATCHED -> HTTPCaller
    NOT_MATCHED -> AttributeManager
HTTPCaller
    TARGET_ATTR = gdacs_geogson
    STATUS_CODE_ATTR = _http_status_code
    HTTP_METHOD = GET
    VERIFY_SSL_CERTIFICATES = Yes
    USE_COOKIES = No
    TARGET_URL = @Value(gdacs_geojson_link)
    TARGET_ATTR_ENCODING = auto-detect
    FOLLOW_REDIRECTS = Yes
    RESPONSE_HEADER_LIST_ATTR = _headers
    SAVE_FILE = Attribute
    TRANSFER_TIMEOUT_LENGTH = 90
    ERROR_ATTR = _error
    CONNECTION_TIMEOUT_LENGTH = 60
    -> AttributeManager
    <Rejected> -> AttributeManager
AttributeManager
    ATTR_TABLE:
      RENAME_SET_VALUE Title > title
      RENAME_SET_VALUE Summary > summary
      RENAME_SET_VALUE Id > id
      RENAME_SET_VALUE Copyright > copyright
      RENAME_SET_VALUE PublishedDate > publisheddate
      RENAME_SET_VALUE LastUpdate > lastupdate
      RENAME_SET_VALUE Category > category
      RENAME_SET_VALUE Author > author
      RENAME_SET_VALUE Content > content
      RENAME_SET_VALUE LinkURI > linkurl
      RENAME_SET_VALUE _georss_feature_number > georss_feature_number
      REMOVE _error
      REMOVE _headers{}.name
      REMOVE _headers{}.value
      REMOVE _http_status_code
    -> DateFormatter
Note: From time zone format to iso date
DateFormatter
    SRCFMT = Unknown - Automatic Detection
    INVALID_DATE_VALUE = _FME_NO_OP_
    DATE_ATTR = gdacs_fromdate,publisheddate,lastupdate,gdacs_todate
    FMT = ISO Date (%Y-%m-%d)
    -> DuplicateFilter_3
DuplicateFilter_3
    KEYATTR = gdacs_eventid publisheddate
    INPUT_ORDERED_CHOICE = No
    UNIQUE -> FeatureMerger [REQUESTOR]
monitoring_platform.gdacs_data (reader POSTGRES_1)
    attributes: title text, summary text, id text, copyright text, publisheddate date, lastupdate date, category text, author text, content text, linkurl text, gdacs_country text, gdacs_cap text, gdacs_alertlevel text, gdacs_episodeid text, gdacs_eventid int4, gdacs_eventname text, gdacs_eventtype text, gdacs_fromdate date, gdacs_gtslink text, gdacs_todate date, gdacs_version text, gdacs_year int4, gdacs_glide text, gdacs_vulnerability text, gdacs_population text, gdacs_severity text, gdacs_resources text, gdacs_geojson_link text, gdacs_geogson text
    -> DateFormatter_2
DateFormatter_2
    SRCFMT = Unknown - Automatic Detection
    INVALID_DATE_VALUE = _FME_NO_OP_
    DATE_ATTR = publisheddate
    FMT = ISO Date (%Y-%m-%d)
    -> DuplicateFilter_2
DuplicateFilter_2
    KEYATTR = gdacs_eventid publisheddate
    INPUT_ORDERED_CHOICE = No
    UNIQUE -> FeatureMerger [SUPPLIER]
FeatureMerger
    PROCESS_DUPS = No
    SUPPLIERS_FIRST = No
    JOIN_KEYS = @Value(gdacs_eventid) @Value(gdacs_eventid) AUTO @Value(publisheddate) @Value(publisheddate) AUTO
    ATTR_CONFLICT_RES = Use Requestor
    IGNORE_NULLS = No
    ATTR_ACCUM_MODE = Merge Supplier
    REJECT_NULL_MISSING_KEYS = No
    MERGE_TYPE = Attributes Only
    UNMERGED_REQUESTOR -> monitoring_platform.gdacs_data (writer POSTGRES_2)
monitoring_platform.gdacs_data (writer POSTGRES_2)
    attributes: title text, summary text, id text, copyright text, publisheddate date, lastupdate date, category text, author text, content text, linkurl text, georss_feature_number text, gdacs_country text, gdacs_cap text, gdacs_alertlevel text, gdacs_episodeid text, gdacs_eventid int4, gdacs_eventname text, gdacs_eventtype text, gdacs_fromdate date, gdacs_gtslink text, gdacs_todate date, gdacs_version text, gdacs_year int4, gdacs_glide text, gdacs_vulnerability text, gdacs_population text, gdacs_severity text, gdacs_resources text, gdacs_geojson_link text, gdacs_geogson text

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

INPUT (input)
    -> OUTPUT (output)
    -> Sampler
Note: Take the first input feature
Sampler
    RATE = 1
    SAMPLE_TYPE_LONG = First N Features
    SAMPLE_MODE = No
    SAMPLED -> StatisticsCalculator
OUTPUT (output)
Creator
    NUM = 1
    GEOMTYPE = Geometry Object
    CREATED -> StatisticsCalculator
Note: Count received features
StatisticsCalculator
    PREPEND_ATTR_NAME_CHOICE = For multiple results only
    COMPUTE_HISTOGRAM = NO
    COUNT_ATTR = NFT_count
    STATS_ATTRS = no_features
    SUMMARY -> Tester_2
Note: If the number of features is equal / to 1, we had no feature coming / through the Input port
Tester_2
    TEST_DESCRIPTION = ""
    BOOL_OP = OR
    TEST_CLAUSE = TEST @Value(NFT_count) = 1
    TEST_MODE = Automatic
    PASSED -> AttributeCreator
Note: Provide an attribute for filtering
AttributeCreator
    ATTR_TABLE = SET_TO no_features = true
    -> NOINPUT (output)
NOINPUT (output)

FME custom transformer IDMC_GDACS_Downloader

Input (input)
    -> NoFeaturesTester
NoFeaturesTester
    NOINPUT -> AttributeCreator
    -> AttributeCreator
AttributeCreator
    ATTR_TABLE = SET_TO url = http://www.gdacs.org/xml/rss_7d.xml
    -> GeoRSSFeatureReader
GeoRSSFeatureReader
    GEORSS_ATTR = url
    INVALID_GEORSS_CHOICES = No
    GEORSS_MODE = NORMAL
    FEAT_NUM = _georss_feature_number
    MERGE_CHOICES = No
    ENTRY -> Output (output)
Output (output)
PythonCaller_Archive [off]
    PYTHONSOURCE:
      # GDACS PythonCaller template leonardo.milano@idmc.ch - python 3
      from fmeobjects import *
      #import pandas as pd
      from datetime import timedelta, date

      class FeatureProcessor(object):
          def __init__(self):
              pass

          def input(self, feature):
              year=feature.getAttribute('year')
              url = "http://www.gdacs.org/rss.aspx?profile=ARCHIVE&fromarchive=true&from={}&to={}"

              def daterange(start_date, end_date):
                  for n in range(int ((end_date - start_date).days)):
                      yield start_date + timedelta(n)

              start_date = date(int(year), 1, 1)
              end_date   = date(int(year)+1, 1, 1)
              end_date   = date(int(year), 1, 10)

              for single_date in daterange(start_date, end_date):
                  new_url = url.format(single_date,single_date)
                  feature.setAttribute('url',new_url)
                  self.pyoutput(feature)
              #url='http://www.gdacs.org/xml/rss_7d.xml'
              #feature.setAttribute('url',new_url)
              #self.pyoutput(feature)

          def close(self):
              pass
    PYTHONSYMBOL = FeatureProcessor
